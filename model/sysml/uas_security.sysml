// GENERATED by tools/gen_sysml.py from data/*.csv. Do not edit by hand.
// Threats are concerns; requirements frame their parent threats and are
// satisfied by their allocated component; verification cases verify them.
package UAS_Security {
    private import ScalarValues::*;
    private import UAS_Architecture::*;

    enum def MissionImpact { enum 'MI-1'; enum 'MI-2'; enum 'MI-3'; enum 'MI-4'; }
    enum def StrideCategory { enum <S> 'spoofing'; enum <T> 'tampering'; enum <R> 'repudiation'; enum <I> 'informationDisclosure'; enum <D> 'denialOfService'; enum <E> 'elevationOfPrivilege'; }
    enum def Disposition { enum 'mitigate'; enum 'accept'; }
    enum def VerificationMethod { enum 'inspection'; enum 'analysis'; enum 'demonstration'; enum 'test'; }

    concern def Threat {
        attribute missionImpact : MissionImpact;
        attribute stride : StrideCategory;
        attribute disposition : Disposition;
    }
    requirement def SecurityRequirement {
        attribute method : VerificationMethod;
        attribute evidenceRepo : String;
        attribute resiliencyApproach : String[0..*];
    }
    verification def SecurityVerification {
        attribute method : VerificationMethod;
        attribute evidenceRepo : String;
    }

    // 66 threats (docs/05-threat-model.md)
    concern 'THR-001' : Threat {
        doc /* Spoofed GCS heartbeats suppress the data-link-loss failsafe. PX4 accepts HEARTBEAT unsigned on every link and derives GCS liveness from MAV_TYPE_GCS heartbeats. While the real GCS link is jammed or down, an adversary who can deliver MAVLink to any FC link impersonates the GCS, so the data-link-loss failsafe (DD-05) never triggers and the vehicle flies on without C2 or automatic return. Residual after SR-001: a compromised CC or GCS, both already inside the C2 trust base. */
        attribute :>> missionImpact = MissionImpact::'MI-1';
        attribute :>> stride = StrideCategory::'spoofing';
        attribute :>> disposition = Disposition::'mitigate';
    }
    dependency from 'THR-001' to UAS_Architecture::'CMP-GCS';
    concern 'THR-002' : Threat {
        doc /* Commands reach the FC outside the modeled C2 path. An enabled uXRCE-DDS client or an unused MAVLink instance (the px4_fmu-v6x defaults enable MAVLink on Ethernet) gives a peer a path to the FC that bypasses the CC. MAVLink signing does not cover uXRCE-DDS at all. */
        attribute :>> missionImpact = MissionImpact::'MI-1';
        attribute :>> stride = StrideCategory::'spoofing';
        attribute :>> disposition = Disposition::'mitigate';
    }
    dependency from 'THR-002' to UAS_Architecture::'CMP-FC';
    concern 'THR-003' : Threat {
        doc /* Privileged MAVLink services used to reconfigure the FC. A peer that can send signed MAVLink (any key holder, or a compromised CC or GCS) uses the MAVLink shell (SERIAL_CONTROL), MAVLink FTP or parameter writes to change failsafes, delete files or run commands on the FC. Residual: CC-originated commands and the USB maintenance link are not filtered. */
        attribute :>> missionImpact = MissionImpact::'MI-1';
        attribute :>> stride = StrideCategory::'tampering';
        attribute :>> disposition = Disposition::'mitigate';
    }
    dependency from 'THR-003' to UAS_Architecture::'CMP-FC';
    concern 'THR-004' : Threat {
        doc /* Signed commands cannot be attributed to a key holder. All holders share one signing key, so the FC cannot tell whether the GCS, CC or MSS signed a command. MAVLink alone cannot show who issued it. */
        attribute :>> missionImpact = MissionImpact::'MI-3';
        attribute :>> stride = StrideCategory::'repudiation';
        attribute :>> disposition = Disposition::'mitigate';
    }
    dependency from 'THR-004' to UAS_Architecture::'CMP-FC';
    concern 'THR-005' : Threat {
        doc /* MAVLink flood on the CC-FC link degrades the FC. A malfunctioning or compromised CC process, or a tap on the UART, floods the FC with MAVLink traffic and starves message handling. Residual: a fully compromised CC can bypass the rate limit. */
        attribute :>> missionImpact = MissionImpact::'MI-2';
        attribute :>> stride = StrideCategory::'denialOfService';
        attribute :>> disposition = Disposition::'mitigate';
    }
    dependency from 'THR-005' to UAS_Architecture::'CMP-FC';
    concern 'THR-006' : Threat {
        doc /* Memory-safety flaw in FC MAVLink handling exploited. Crafted MAVLink exploits a parsing flaw in PX4 and gains code execution on the FC. The MAVLink frame parser runs on unauthenticated input; the PX4 v1.17 release notes list MAVLink FTP path-traversal hardening, so flaws of this class occur. */
        attribute :>> missionImpact = MissionImpact::'MI-1';
        attribute :>> stride = StrideCategory::'elevationOfPrivilege';
        attribute :>> disposition = Disposition::'mitigate';
    }
    dependency from 'THR-006' to UAS_Architecture::'CMP-FC';
    concern 'THR-007' : Threat {
        doc /* Vehicle impersonated with a stolen CC WireGuard key. An adversary holding the CC's WireGuard private key, for example from a captured vehicle, poses as the vehicle to the GCS and feeds it false telemetry and video. */
        attribute :>> missionImpact = MissionImpact::'MI-2';
        attribute :>> stride = StrideCategory::'spoofing';
        attribute :>> disposition = Disposition::'mitigate';
    }
    dependency from 'THR-007' to UAS_Architecture::'CMP-CC';
    concern 'THR-008' : Threat {
        doc /* Persistent modification of CC software. An adversary with physical access, a malicious update or a foothold on the CC modifies its boot chain, root filesystem or configuration so the compromise survives reboot. */
        attribute :>> missionImpact = MissionImpact::'MI-1';
        attribute :>> stride = StrideCategory::'tampering';
        attribute :>> disposition = Disposition::'mitigate';
    }
    dependency from 'THR-008' to UAS_Architecture::'CMP-CC';
    concern 'THR-009' : Threat {
        doc /* CC failure removes all C2. All C2 passes through the CC (DD-01), so a CC crash, hang or power fault cuts the vehicle off from the GCS. */
        attribute :>> missionImpact = MissionImpact::'MI-2';
        attribute :>> stride = StrideCategory::'denialOfService';
        attribute :>> disposition = Disposition::'mitigate';
    }
    dependency from 'THR-009' to UAS_Architecture::'CMP-CC';
    concern 'THR-010' : Threat {
        doc /* Code execution on the CC yields full vehicle C2. An adversary who gains code execution on the CC, through a flaw in a network-facing or media service or a malicious peripheral, reads the shared signing key and signs any command to the FC. Top threat of the architecture (section 4.2). Residual: full CC compromise still yields C2, inherent to PX4's shared-key signing. */
        attribute :>> missionImpact = MissionImpact::'MI-1';
        attribute :>> stride = StrideCategory::'elevationOfPrivilege';
        attribute :>> disposition = Disposition::'mitigate';
    }
    dependency from 'THR-010' to UAS_Architecture::'CMP-CC';
    concern 'THR-011' : Threat {
        doc /* Tampered payload attacks the CC over USB. A payload with modified firmware enumerates as an unexpected USB device class, such as a keyboard or network adapter, to attack the CC. */
        attribute :>> missionImpact = MissionImpact::'MI-1';
        attribute :>> stride = StrideCategory::'tampering';
        attribute :>> disposition = Disposition::'mitigate';
    }
    dependency from 'THR-011' to UAS_Architecture::'CMP-PL';
    concern 'THR-012' : Threat {
        doc /* Tampered or counterfeit navigation module. A GNSS or compass module with modified firmware, introduced through the supply chain or maintenance, reports false position or heading. Residual: a modification made before receipt that leaves the reported firmware version unchanged. */
        attribute :>> missionImpact = MissionImpact::'MI-1';
        attribute :>> stride = StrideCategory::'tampering';
        attribute :>> disposition = Disposition::'mitigate';
    }
    dependency from 'THR-012' to UAS_Architecture::'CMP-NAV';
    concern 'THR-013' : Threat {
        doc /* Tampered ESC firmware commands unsafe thrust. ESC firmware modified through the supply chain, or over DroneCAN by a compromised node, ignores or distorts FC commands. */
        attribute :>> missionImpact = MissionImpact::'MI-1';
        attribute :>> stride = StrideCategory::'tampering';
        attribute :>> disposition = Disposition::'mitigate';
    }
    dependency from 'THR-013' to UAS_Architecture::'CMP-ACT';
    concern 'THR-014' : Threat {
        doc /* Compromised air radio attacks the CC. An air radio compromised over RF or through its own firmware sits on the CC's Ethernet segment and attacks CC services directly. */
        attribute :>> missionImpact = MissionImpact::'MI-1';
        attribute :>> stride = StrideCategory::'elevationOfPrivilege';
        attribute :>> disposition = Disposition::'mitigate';
    }
    dependency from 'THR-014' to UAS_Architecture::'CMP-RAD-A';
    concern 'THR-015' : Threat {
        doc /* Compromised ground radio attacks the GCS host. A ground radio compromised over RF or through its own firmware sits on the GCS host's network interface and attacks GCS services directly. */
        attribute :>> missionImpact = MissionImpact::'MI-1';
        attribute :>> stride = StrideCategory::'elevationOfPrivilege';
        attribute :>> disposition = Disposition::'mitigate';
    }
    dependency from 'THR-015' to UAS_Architecture::'CMP-RAD-G';
    concern 'THR-016' : Threat {
        doc /* Stolen or unattended GCS used to command the vehicle. Someone with physical access to an unattended or stolen GCS laptop uses its keys and session to command the vehicle. */
        attribute :>> missionImpact = MissionImpact::'MI-1';
        attribute :>> stride = StrideCategory::'spoofing';
        attribute :>> disposition = Disposition::'mitigate';
    }
    dependency from 'THR-016' to UAS_Architecture::'CMP-GCS';
    concern 'THR-017' : Threat {
        doc /* Tampered GCS software. A modified QGroundControl build or operating-system package, inserted upstream or during installation, forges commands or misreports telemetry while holding the signing key. */
        attribute :>> missionImpact = MissionImpact::'MI-1';
        attribute :>> stride = StrideCategory::'tampering';
        attribute :>> disposition = Disposition::'mitigate';
    }
    dependency from 'THR-017' to UAS_Architecture::'CMP-GCS';
    concern 'THR-018' : Threat {
        doc /* Operator actions cannot be attributed. Without a per-operator record, the GCS cannot show which operator issued a command. */
        attribute :>> missionImpact = MissionImpact::'MI-3';
        attribute :>> stride = StrideCategory::'repudiation';
        attribute :>> disposition = Disposition::'mitigate';
    }
    dependency from 'THR-018' to UAS_Architecture::'CMP-GCS';
    concern 'THR-019' : Threat {
        doc /* Malware from unrelated use compromises the GCS. Email, web browsing, removable media or other networks used on the GCS deliver malware that obtains the signing and WireGuard keys. */
        attribute :>> missionImpact = MissionImpact::'MI-1';
        attribute :>> stride = StrideCategory::'elevationOfPrivilege';
        attribute :>> disposition = Disposition::'mitigate';
    }
    dependency from 'THR-019' to UAS_Architecture::'CMP-GCS';
    concern 'THR-020' : Threat {
        doc /* Unauthorized use of the MSS. Someone with access to an unattended MSS uses it to load software or provision keys. */
        attribute :>> missionImpact = MissionImpact::'MI-1';
        attribute :>> stride = StrideCategory::'spoofing';
        attribute :>> disposition = Disposition::'mitigate';
    }
    dependency from 'THR-020' to UAS_Architecture::'CMP-MSS';
    concern 'THR-021' : Threat {
        doc /* Build environment inserts malicious code into signed artifacts. A compromised build host or toolchain alters firmware or images before signing, so devices accept them as genuine. */
        attribute :>> missionImpact = MissionImpact::'MI-1';
        attribute :>> stride = StrideCategory::'tampering';
        attribute :>> disposition = Disposition::'mitigate';
    }
    dependency from 'THR-021' to UAS_Architecture::'CMP-MSS';
    concern 'THR-022' : Threat {
        doc /* Maintenance actions cannot be attributed. Without a per-maintainer record, the MSS cannot show who loaded software or provisioned keys. */
        attribute :>> missionImpact = MissionImpact::'MI-3';
        attribute :>> stride = StrideCategory::'repudiation';
        attribute :>> disposition = Disposition::'mitigate';
    }
    dependency from 'THR-022' to UAS_Architecture::'CMP-MSS';
    concern 'THR-023' : Threat {
        doc /* MSS compromised through its online connection. The MSS fetches upstream sources (DF-16). Malware arriving that way gains access to master key material and to the maintenance links into the vehicle. */
        attribute :>> missionImpact = MissionImpact::'MI-1';
        attribute :>> stride = StrideCategory::'elevationOfPrivilege';
        attribute :>> disposition = Disposition::'mitigate';
    }
    dependency from 'THR-023' to UAS_Architecture::'CMP-MSS';
    concern 'THR-024' : Threat {
        doc /* GNSS spoofing diverts the vehicle. Counterfeit civil GNSS signals shift the position estimate and steer the vehicle off its route or into a hazard. PX4 alerts on spoofing the receiver reports, and with EKF2_GPS_CHECK bit 9 set it also stops relying on that GNSS data. Residual: spoofing the receiver does not report goes unflagged. */
        attribute :>> missionImpact = MissionImpact::'MI-1';
        attribute :>> stride = StrideCategory::'spoofing';
        attribute :>> disposition = Disposition::'mitigate';
    }
    dependency from 'THR-024' to UAS_Architecture::'EE-GNSS';
    concern 'THR-025' : Threat {
        doc /* Impersonated upstream source. A typosquatted package, a dependency-confusion name or a compromised mirror supplies code that appears to come from a legitimate project. */
        attribute :>> missionImpact = MissionImpact::'MI-1';
        attribute :>> stride = StrideCategory::'spoofing';
        attribute :>> disposition = Disposition::'mitigate';
    }
    dependency from 'THR-025' to UAS_Architecture::'EE-UPSTREAM';
    concern 'THR-026' : Threat {
        doc /* Signing key read from the FC's SD card. Anyone with brief physical access to the SD card copies the 40-byte key file and becomes a key holder. The key alone does not reach the FC over RF (SR-001), but it does over USB or a telemetry port. */
        attribute :>> missionImpact = MissionImpact::'MI-1';
        attribute :>> stride = StrideCategory::'informationDisclosure';
        attribute :>> disposition = Disposition::'mitigate';
    }
    dependency from 'THR-026' to UAS_Architecture::'DS-FC-KEY';
    concern 'THR-027' : Threat {
        doc /* Signing key file replaced or deleted. Replacing the key file installs an adversary's key and locks out the GCS. Deleting it disables signing on every link at the next boot. */
        attribute :>> missionImpact = MissionImpact::'MI-1';
        attribute :>> stride = StrideCategory::'tampering';
        attribute :>> disposition = Disposition::'mitigate';
    }
    dependency from 'THR-027' to UAS_Architecture::'DS-FC-KEY';
    concern 'THR-028' : Threat {
        doc /* Flight logs reveal mission areas and routes. ULogs on the SD card of a captured vehicle show where it flew and what it did. */
        attribute :>> missionImpact = MissionImpact::'MI-2';
        attribute :>> stride = StrideCategory::'informationDisclosure';
        attribute :>> disposition = Disposition::'mitigate';
    }
    dependency from 'THR-028' to UAS_Architecture::'DS-FC-LOG';
    concern 'THR-029' : Threat {
        doc /* Flight logs altered or deleted to hide activity. A peer with MAVLink FTP access edits or deletes ULogs remotely. Residual: anyone holding the SD card can do the same. */
        attribute :>> missionImpact = MissionImpact::'MI-3';
        attribute :>> stride = StrideCategory::'tampering';
        attribute :>> disposition = Disposition::'mitigate';
    }
    dependency from 'THR-029' to UAS_Architecture::'DS-FC-LOG';
    concern 'THR-030' : Threat {
        doc /* FC firmware or parameters modified through the bootloader or debug port. With physical access, an adversary flashes modified PX4 firmware over USB or rewrites flash over SWD. */
        attribute :>> missionImpact = MissionImpact::'MI-1';
        attribute :>> stride = StrideCategory::'tampering';
        attribute :>> disposition = Disposition::'mitigate';
    }
    dependency from 'THR-030' to UAS_Architecture::'DS-FC-FW';
    concern 'THR-031' : Threat {
        doc /* Firmware and parameters extracted from a captured FC. An adversary reads the PX4 firmware image and parameter set from a captured FC. */
        comment acceptanceRationale /* PX4 is open source and the parameter baseline is published in P1. The only secret on the FC is the signing key, covered by THR-026. */
        attribute :>> missionImpact = MissionImpact::'MI-4';
        attribute :>> stride = StrideCategory::'informationDisclosure';
        attribute :>> disposition = Disposition::'accept';
    }
    dependency from 'THR-031' to UAS_Architecture::'DS-FC-FW';
    concern 'THR-032' : Threat {
        doc /* CC storage rewritten offline. An adversary removes or reflashes the CC's storage to replace the boot chain or root filesystem. */
        attribute :>> missionImpact = MissionImpact::'MI-1';
        attribute :>> stride = StrideCategory::'tampering';
        attribute :>> disposition = Disposition::'mitigate';
    }
    dependency from 'THR-032' to UAS_Architecture::'DS-CC-SYS';
    concern 'THR-033' : Threat {
        doc /* CC system image read from a captured vehicle. An adversary copies the CC's root filesystem and configuration from a captured vehicle. */
        comment acceptanceRationale /* The image holds open-source software and configuration documented in P1 and P4. It contains no secrets; credentials are kept in DS-CC-CRED (THR-034). */
        attribute :>> missionImpact = MissionImpact::'MI-4';
        attribute :>> stride = StrideCategory::'informationDisclosure';
        attribute :>> disposition = Disposition::'accept';
    }
    dependency from 'THR-033' to UAS_Architecture::'DS-CC-SYS';
    concern 'THR-034' : Threat {
        doc /* Keys extracted from a captured CC. An adversary extracts the CC's copy of the signing key and its WireGuard private key from a captured vehicle. Residual after SR-010: with time and tools, an adversary can probe the bus between the SoC and the TPM, where an encrypted unseal session (P2 SR-010.4) stops passive reads only; or, if the TPM can be reset without resetting the CC, reset it and replay approved measurements to unseal the keys (P2 A2-02). Active bus and fault-injection attacks are P5's scope. */
        attribute :>> missionImpact = MissionImpact::'MI-1';
        attribute :>> stride = StrideCategory::'informationDisclosure';
        attribute :>> disposition = Disposition::'mitigate';
    }
    dependency from 'THR-034' to UAS_Architecture::'DS-CC-CRED';
    concern 'THR-035' : Threat {
        doc /* CC trust anchors replaced. Replacing the stored GCS public key or signing key makes an adversary's GCS a trusted peer. */
        attribute :>> missionImpact = MissionImpact::'MI-1';
        attribute :>> stride = StrideCategory::'tampering';
        attribute :>> disposition = Disposition::'mitigate';
    }
    dependency from 'THR-035' to UAS_Architecture::'DS-CC-CRED';
    concern 'THR-036' : Threat {
        doc /* Imagery and mission plan read from a captured vehicle. Survey imagery and the active mission plan are read from the CC's storage. */
        attribute :>> missionImpact = MissionImpact::'MI-2';
        attribute :>> stride = StrideCategory::'informationDisclosure';
        attribute :>> disposition = Disposition::'mitigate';
    }
    dependency from 'THR-036' to UAS_Architecture::'DS-CC-DATA';
    concern 'THR-037' : Threat {
        doc /* Keys stolen from a lost or stolen GCS. The signing key and the GCS WireGuard private key are copied from the laptop's disk. */
        attribute :>> missionImpact = MissionImpact::'MI-1';
        attribute :>> stride = StrideCategory::'informationDisclosure';
        attribute :>> disposition = Disposition::'mitigate';
    }
    dependency from 'THR-037' to UAS_Architecture::'DS-GCS-CRED';
    concern 'THR-038' : Threat {
        doc /* Mission plans and imagery disclosed from the GCS. Mission plans, telemetry logs and received imagery are read from the laptop's disk. */
        attribute :>> missionImpact = MissionImpact::'MI-2';
        attribute :>> stride = StrideCategory::'informationDisclosure';
        attribute :>> disposition = Disposition::'mitigate';
    }
    dependency from 'THR-038' to UAS_Architecture::'DS-GCS-DATA';
    concern 'THR-039' : Threat {
        doc /* Master key material stolen from the MSS. The master signing key, WireGuard key pairs and software signing keys are copied from the MSS. */
        attribute :>> missionImpact = MissionImpact::'MI-1';
        attribute :>> stride = StrideCategory::'informationDisclosure';
        attribute :>> disposition = Disposition::'mitigate';
    }
    dependency from 'THR-039' to UAS_Architecture::'DS-MSS-KEYS';
    concern 'THR-040' : Threat {
        doc /* Software signing key lost. If the firmware signing private key is lost, devices that trust it can no longer be updated. PX4's secure-boot guide warns that recovery then needs a debug probe. */
        attribute :>> missionImpact = MissionImpact::'MI-2';
        attribute :>> stride = StrideCategory::'denialOfService';
        attribute :>> disposition = Disposition::'mitigate';
    }
    dependency from 'THR-040' to UAS_Architecture::'DS-MSS-KEYS';
    concern 'THR-041' : Threat {
        doc /* Release artifacts tampered before loading. Built images, firmware or SBOMs are modified in MSS storage between build and load. */
        attribute :>> missionImpact = MissionImpact::'MI-1';
        attribute :>> stride = StrideCategory::'tampering';
        attribute :>> disposition = Disposition::'mitigate';
    }
    dependency from 'THR-041' to UAS_Architecture::'DS-MSS-ART';
    concern 'THR-042' : Threat {
        doc /* Commands injected or altered over the RF uplink. An RF-proximate adversary injects or modifies commands, mission uploads or parameter writes on the air-ground link. */
        attribute :>> missionImpact = MissionImpact::'MI-1';
        attribute :>> stride = StrideCategory::'tampering';
        attribute :>> disposition = Disposition::'mitigate';
    }
    dependency from 'THR-042' to UAS_Architecture::'DF-01';
    concern 'THR-043' : Threat {
        doc /* Commands and mission uploads read over RF. An RF-proximate adversary records the uplink and reads commands and flight plans. */
        attribute :>> missionImpact = MissionImpact::'MI-2';
        attribute :>> stride = StrideCategory::'informationDisclosure';
        attribute :>> disposition = Disposition::'mitigate';
    }
    dependency from 'THR-043' to UAS_Architecture::'DF-01';
    concern 'THR-044' : Threat {
        doc /* RF jamming of the uplink. Jamming blocks the uplink. Residual: jamming itself cannot be prevented (A-12); the vehicle returns under the data-link-loss failsafe. */
        attribute :>> missionImpact = MissionImpact::'MI-2';
        attribute :>> stride = StrideCategory::'denialOfService';
        attribute :>> disposition = Disposition::'mitigate';
    }
    dependency from 'THR-044' to UAS_Architecture::'DF-01';
    concern 'THR-045' : Threat {
        doc /* Spoofed telemetry misleads the operator. Forged or altered telemetry shows the operator a false vehicle state. */
        attribute :>> missionImpact = MissionImpact::'MI-2';
        attribute :>> stride = StrideCategory::'tampering';
        attribute :>> disposition = Disposition::'mitigate';
    }
    dependency from 'THR-045' to UAS_Architecture::'DF-02';
    concern 'THR-046' : Threat {
        doc /* Telemetry read over RF. An RF-proximate adversary records the downlink and reads vehicle position and status. */
        attribute :>> missionImpact = MissionImpact::'MI-2';
        attribute :>> stride = StrideCategory::'informationDisclosure';
        attribute :>> disposition = Disposition::'mitigate';
    }
    dependency from 'THR-046' to UAS_Architecture::'DF-02';
    concern 'THR-047' : Threat {
        doc /* RF emissions reveal vehicle and GCS locations. Transmissions reveal that the vehicle and GCS are operating, and direction finding locates them. */
        comment acceptanceRationale /* WireGuard hides content, not the existence, timing or direction of transmissions. Emission control belongs to the waveform and EW, both out of scope (A-12). */
        attribute :>> missionImpact = MissionImpact::'MI-2';
        attribute :>> stride = StrideCategory::'informationDisclosure';
        attribute :>> disposition = Disposition::'accept';
    }
    dependency from 'THR-047' to UAS_Architecture::'DF-02';
    concern 'THR-048' : Threat {
        doc /* Video intercepted over RF. An RF-proximate adversary records the downlink and recovers payload video. */
        attribute :>> missionImpact = MissionImpact::'MI-2';
        attribute :>> stride = StrideCategory::'informationDisclosure';
        attribute :>> disposition = Disposition::'mitigate';
    }
    dependency from 'THR-048' to UAS_Architecture::'DF-03';
    concern 'THR-049' : Threat {
        doc /* Unsigned or forged frames injected on the CC-FC UART. A tap fitted to the UART injects frames. Signing rejects them unless the adversary holds the key, except for the four messages PX4 accepts unsigned. */
        attribute :>> missionImpact = MissionImpact::'MI-1';
        attribute :>> stride = StrideCategory::'tampering';
        attribute :>> disposition = Disposition::'mitigate';
    }
    dependency from 'THR-049' to UAS_Architecture::'DF-04';
    concern 'THR-050' : Threat {
        doc /* Spoofed ADSB_VEHICLE or COLLISION messages. PX4 accepts both unsigned. Spoofed ADSB_VEHICLE reports drive traffic avoidance (NAV_TRAFF_AVOID); PX4 v1.18.0-rc1 has no receive handler for COLLISION. The system has no ADS-B receiver, so neither message has a legitimate source. */
        attribute :>> missionImpact = MissionImpact::'MI-3';
        attribute :>> stride = StrideCategory::'tampering';
        attribute :>> disposition = Disposition::'mitigate';
    }
    dependency from 'THR-050' to UAS_Architecture::'DF-04';
    concern 'THR-051' : Threat {
        doc /* Spoofed RADIO_STATUS throttles FC telemetry. A spoofed RADIO_STATUS reporting a low transmit buffer cuts the FC's outgoing stream rate by 20% per message, down to 1%, when software throttling is active on that link. The IP radios send no RADIO_STATUS. */
        attribute :>> missionImpact = MissionImpact::'MI-3';
        attribute :>> stride = StrideCategory::'tampering';
        attribute :>> disposition = Disposition::'mitigate';
    }
    dependency from 'THR-051' to UAS_Architecture::'DF-04';
    concern 'THR-052' : Threat {
        doc /* Tampered FC telemetry misleads CC autonomy. Altered or injected telemetry on the FC-to-CC link leads onboard autonomy to act on a false vehicle state. */
        attribute :>> missionImpact = MissionImpact::'MI-2';
        attribute :>> stride = StrideCategory::'tampering';
        attribute :>> disposition = Disposition::'mitigate';
    }
    dependency from 'THR-052' to UAS_Architecture::'DF-05';
    concern 'THR-053' : Threat {
        doc /* Malformed imagery exploits the CC video pipeline. A tampered payload sends a crafted video stream that exploits a parsing flaw in the CC's media pipeline. */
        attribute :>> missionImpact = MissionImpact::'MI-1';
        attribute :>> stride = StrideCategory::'tampering';
        attribute :>> disposition = Disposition::'mitigate';
    }
    dependency from 'THR-053' to UAS_Architecture::'DF-06';
    concern 'THR-054' : Threat {
        doc /* GNSS jamming denies position. Jamming removes or degrades GNSS. PX4 alerts on jamming the receiver reports, but treats it as a failed GNSS check only when EKF2_GPS_CHECK bit 11 is set, which is off by default. COM_POS_LOW_ACT (default Return) acts on low position accuracy only in mission or loiter modes. */
        attribute :>> missionImpact = MissionImpact::'MI-2';
        attribute :>> stride = StrideCategory::'denialOfService';
        attribute :>> disposition = Disposition::'mitigate';
    }
    dependency from 'THR-054' to UAS_Architecture::'DF-07';
    concern 'THR-055' : Threat {
        doc /* False navigation data injected on the NAV-FC wiring. Someone with physical access to the airframe taps the navigation module's wiring and injects false position or heading. */
        attribute :>> missionImpact = MissionImpact::'MI-1';
        attribute :>> stride = StrideCategory::'tampering';
        attribute :>> disposition = Disposition::'mitigate';
    }
    dependency from 'THR-055' to UAS_Architecture::'DF-08';
    concern 'THR-056' : Threat {
        doc /* Actuator commands altered on the FC-ESC wiring. Someone with physical access to the airframe taps the actuator wiring and alters motor commands. */
        attribute :>> missionImpact = MissionImpact::'MI-1';
        attribute :>> stride = StrideCategory::'tampering';
        attribute :>> disposition = Disposition::'mitigate';
    }
    dependency from 'THR-056' to UAS_Architecture::'DF-09';
    concern 'THR-057' : Threat {
        doc /* Unauthorized peer installs the first signing key. Before a key exists, PX4 v1.18 accepts SETUP_SIGNING unsigned on any link. A peer that reaches any FC link first installs its own key and locks out the GCS until the SD card is cleared. Source: the v1.18 change that accepts SETUP_SIGNING on any link instead of USB only. */
        attribute :>> missionImpact = MissionImpact::'MI-2';
        attribute :>> stride = StrideCategory::'tampering';
        attribute :>> disposition = Disposition::'mitigate';
    }
    dependency from 'THR-057' to UAS_Architecture::'DF-11';
    concern 'THR-058' : Threat {
        doc /* Unsigned firmware loaded through the USB bootloader. The PX4 bootloader accepts any firmware image over USB unless secure boot is enabled. */
        attribute :>> missionImpact = MissionImpact::'MI-1';
        attribute :>> stride = StrideCategory::'tampering';
        attribute :>> disposition = Disposition::'mitigate';
    }
    dependency from 'THR-058' to UAS_Architecture::'DF-11';
    concern 'THR-059' : Threat {
        doc /* Malicious image or credentials loaded into the CC. A rogue maintenance device, or a compromised MSS, loads a modified image or replacement credentials over the maintenance link. */
        attribute :>> missionImpact = MissionImpact::'MI-1';
        attribute :>> stride = StrideCategory::'tampering';
        attribute :>> disposition = Disposition::'mitigate';
    }
    dependency from 'THR-059' to UAS_Architecture::'DF-12';
    concern 'THR-060' : Threat {
        doc /* Keys exposed on removable media during GCS provisioning. Signing and WireGuard keys copied to removable media for the GCS can be lost, copied or left behind. */
        attribute :>> missionImpact = MissionImpact::'MI-1';
        attribute :>> stride = StrideCategory::'informationDisclosure';
        attribute :>> disposition = Disposition::'mitigate';
    }
    dependency from 'THR-060' to UAS_Architecture::'DF-13';
    concern 'THR-061' : Threat {
        doc /* Crafted offload data exploits the MSS. A compromised CC returns crafted imagery or logs that exploit software on the MSS, the host with every key. */
        attribute :>> missionImpact = MissionImpact::'MI-1';
        attribute :>> stride = StrideCategory::'tampering';
        attribute :>> disposition = Disposition::'mitigate';
    }
    dependency from 'THR-061' to UAS_Architecture::'DF-14';
    concern 'THR-062' : Threat {
        doc /* Crafted flight logs exploit MSS log tools. A tampered FC or SD card returns crafted ULogs that exploit log-analysis tools on the MSS. */
        attribute :>> missionImpact = MissionImpact::'MI-1';
        attribute :>> stride = StrideCategory::'tampering';
        attribute :>> disposition = Disposition::'mitigate';
    }
    dependency from 'THR-062' to UAS_Architecture::'DF-15';
    concern 'THR-063' : Threat {
        doc /* Compromised upstream release enters the build. A malicious change in a legitimate upstream project or release (a PX4 submodule, a distribution package or a toolchain) is built into signed artifacts. */
        attribute :>> missionImpact = MissionImpact::'MI-1';
        attribute :>> stride = StrideCategory::'tampering';
        attribute :>> disposition = Disposition::'mitigate';
    }
    dependency from 'THR-063' to UAS_Architecture::'DF-16';
    concern 'THR-064' : Threat {
        doc /* Flaw in PX4's signing implementation lets forged frames through. PX4 states its signing implementation has not been audited, and signing fixes are still landing: PR #28891 (forwarding of signed frames) merged on main on 2026-09-30, after the pinned v1.18.0-rc1. A remaining flaw could let a peer without the key pass signature checks. */
        attribute :>> missionImpact = MissionImpact::'MI-1';
        attribute :>> stride = StrideCategory::'spoofing';
        attribute :>> disposition = Disposition::'mitigate';
    }
    dependency from 'THR-064' to UAS_Architecture::'CMP-FC';
    concern 'THR-065' : Threat {
        doc /* Signed frames replayed after an FC reboot. PX4 notes the on-disk signing timestamp usually stays at its provisioning value, because vehicles are powered off without a graceful shutdown. Assumption, to be checked in VE-02: after a reboot, frames recorded since provisioning may pass the timestamp check. Over RF the adversary sees only WireGuard ciphertext, so recording needs a tap inside the vehicle or a key holder. */
        attribute :>> missionImpact = MissionImpact::'MI-1';
        attribute :>> stride = StrideCategory::'tampering';
        attribute :>> disposition = Disposition::'mitigate';
    }
    dependency from 'THR-065' to UAS_Architecture::'DF-04';
    concern 'THR-066' : Threat {
        doc /* Older signed FC firmware loaded through the USB bootloader. With physical access to the FC's USB port, an adversary loads an older FC firmware release that the project signed, reintroducing a flaw a later release fixed. SR-018 does not stop it: PX4 Bootloader Secure Boot checks only the signature, and the bootloader never reads the creation and expiry dates in image_cert_t (P2 docs/04). Residual after SR-045: the downgrade is detected before arming, not prevented. */
        attribute :>> missionImpact = MissionImpact::'MI-1';
        attribute :>> stride = StrideCategory::'tampering';
        attribute :>> disposition = Disposition::'mitigate';
    }
    dependency from 'THR-066' to UAS_Architecture::'DF-11';

    // 45 requirements (docs/07-requirements.md)
    requirement 'SR-001' : SecurityRequirement {
        doc /* The CC shall discard all traffic on its radio interface except WireGuard traffic from the provisioned GCS peer. */
        comment rationale /* Keeps RF-injected MAVLink, including the four messages PX4 accepts unsigned, from reaching the MAVLink router or the FC (THR-001). Verified by VE-01. */
        frame 'THR-001';
        frame 'THR-006';
        frame 'THR-010';
        frame 'THR-014';
        frame 'THR-042';
        frame 'THR-043';
        frame 'THR-046';
        frame 'THR-048';
        frame 'THR-064';
        frame 'THR-065';
        attribute :>> method = VerificationMethod::'test';
        attribute :>> evidenceRepo = "P3";
        attribute :>> resiliencyApproach = ("Segmentation: Predefined Segmentation", "Deception: Obfuscation", "Coordinated Protection: Calibrated Defense-in-Depth");
    }
    satisfy 'SR-001' by UAS_Architecture::uasSystem.airVehicle.missionComputing.cc;
    requirement 'SR-002' : SecurityRequirement {
        doc /* The GCS shall discard all traffic on its radio interface except WireGuard traffic from the provisioned CC peer. */
        comment rationale /* Mirrors SR-001 on the ground side: RF-injected traffic and a compromised ground radio reach only the WireGuard endpoint. */
        frame 'THR-015';
        frame 'THR-043';
        frame 'THR-045';
        frame 'THR-046';
        frame 'THR-048';
        attribute :>> method = VerificationMethod::'test';
        attribute :>> evidenceRepo = "P3";
        attribute :>> resiliencyApproach = ("Segmentation: Predefined Segmentation", "Deception: Obfuscation", "Coordinated Protection: Calibrated Defense-in-Depth");
    }
    satisfy 'SR-002' by UAS_Architecture::uasSystem.groundSegment.gcs;
    requirement 'SR-003' : SecurityRequirement {
        doc /* The FC shall reject MAVLink messages that are unsigned or not signed with the provisioned key, except HEARTBEAT, RADIO_STATUS, ADSB_VEHICLE and COLLISION. */
        comment rationale /* End-to-end command integrity from GCS to FC, inside the tunnel. The exceptions are PX4's fixed unsigned allowlist. Verified by VE-02. */
        frame 'THR-042';
        frame 'THR-049';
        frame 'THR-064';
        attribute :>> method = VerificationMethod::'demonstration';
        attribute :>> evidenceRepo = "P3";
        attribute :>> resiliencyApproach = ("Substantiated Integrity: Integrity Checks");
    }
    satisfy 'SR-003' by UAS_Architecture::uasSystem.airVehicle.flightCritical.fc;
    requirement 'SR-004' : SecurityRequirement {
        doc /* The FC shall enter Return mode when no GCS heartbeat has been received for COM_DL_LOSS_T = 10 s (NAV_DLL_ACT = 2). */
        comment rationale /* PX4 disables the GCS-loss failsafe by default. Jamming, tunnel loss and CC failure all appear as data-link loss (DD-01, DD-05). 10 s is the PX4 default timeout, kept as the initial value and checked in VE-01. */
        frame 'THR-009';
        frame 'THR-044';
        attribute :>> method = VerificationMethod::'test';
        attribute :>> evidenceRepo = "P3";
        attribute :>> resiliencyApproach = ("Adaptive Response: Dynamic Reconfiguration");
    }
    satisfy 'SR-004' by UAS_Architecture::uasSystem.airVehicle.flightCritical.fc;
    requirement 'SR-005' : SecurityRequirement {
        doc /* The CC shall boot only boot-chain components signed with the project boot key, verified from a hardware root of trust. */
        comment rationale /* Stops persistent modification of the boot chain from surviving a reboot. */
        frame 'THR-008';
        frame 'THR-010';
        frame 'THR-032';
        attribute :>> method = VerificationMethod::'test';
        attribute :>> evidenceRepo = "P2";
        attribute :>> resiliencyApproach = ("Substantiated Integrity: Integrity Checks");
    }
    satisfy 'SR-005' by UAS_Architecture::uasSystem.airVehicle.missionComputing.cc;
    requirement 'SR-006' : SecurityRequirement {
        doc /* The CC shall mount its root filesystem read-only with block-level integrity verification. */
        comment rationale /* Extends the verified boot chain to the root filesystem, so offline or runtime modification is detected when blocks are read. */
        frame 'THR-008';
        frame 'THR-032';
        attribute :>> method = VerificationMethod::'test';
        attribute :>> evidenceRepo = "P4";
        attribute :>> resiliencyApproach = ("Substantiated Integrity: Integrity Checks", "Non-Persistence: Non-Persistent Services");
    }
    satisfy 'SR-006' by UAS_Architecture::uasSystem.airVehicle.missionComputing.cc;
    requirement 'SR-007' : SecurityRequirement {
        doc /* The CC shall install only update images that are signed with the MSS release key and newer than the installed version. */
        comment rationale /* Blocks malicious and rollback images on the maintenance path. */
        frame 'THR-008';
        frame 'THR-041';
        frame 'THR-059';
        attribute :>> method = VerificationMethod::'test';
        attribute :>> evidenceRepo = "P3";
        attribute :>> resiliencyApproach = ("Substantiated Integrity: Provenance Tracking", "Substantiated Integrity: Integrity Checks");
    }
    satisfy 'SR-007' by UAS_Architecture::uasSystem.airVehicle.missionComputing.cc;
    requirement 'SR-008' : SecurityRequirement {
        doc /* The CC shall restrict read access to the MAVLink signing key to a single signing service. */
        comment rationale /* Compromise of the video pipeline, the router or another CC process then does not directly yield the shared key. */
        frame 'THR-010';
        attribute :>> method = VerificationMethod::'test';
        attribute :>> evidenceRepo = "P4";
        attribute :>> resiliencyApproach = ("Privilege Restriction: Trust-Based Privilege Management");
    }
    satisfy 'SR-008' by UAS_Architecture::uasSystem.airVehicle.missionComputing.cc;
    requirement 'SR-009' : SecurityRequirement {
        doc /* The CC shall run the MAVLink router, the command filter and the video pipeline as unprivileged processes confined by a mandatory access control policy. */
        comment rationale /* These processes parse untrusted input from the link and the payload. Confinement limits what an exploited parser can reach. */
        frame 'THR-010';
        frame 'THR-014';
        frame 'THR-053';
        attribute :>> method = VerificationMethod::'test';
        attribute :>> evidenceRepo = "P4";
        attribute :>> resiliencyApproach = ("Privilege Restriction: Trust-Based Privilege Management", "Segmentation: Predefined Segmentation");
    }
    satisfy 'SR-009' by UAS_Architecture::uasSystem.airVehicle.missionComputing.cc;
    requirement 'SR-010' : SecurityRequirement {
        doc /* The CC shall seal its WireGuard private key and its copy of the signing key to its TPM, bound to the measured boot state. */
        comment rationale /* Keys cannot be read from removed storage, and a modified boot chain cannot unseal them. */
        frame 'THR-007';
        frame 'THR-034';
        frame 'THR-035';
        attribute :>> method = VerificationMethod::'test';
        attribute :>> evidenceRepo = "P2";
        attribute :>> resiliencyApproach = ("Privilege Restriction: Attribute-Based Usage Restriction", "Substantiated Integrity: Integrity Checks");
    }
    satisfy 'SR-010' by UAS_Architecture::uasSystem.airVehicle.missionComputing.cc;
    requirement 'SR-011' : SecurityRequirement {
        doc /* The CC shall forward from the GCS tunnel to the FC only messages and commands on the approved allowlist, which excludes SERIAL_CONTROL, FILE_TRANSFER_PROTOCOL, SETUP_SIGNING, RADIO_STATUS, ADSB_VEHICLE and COLLISION. */
        comment rationale /* Implements DD-04: removes shell, file and key-management services and the unsigned-allowlist messages from what the link can reach. QGroundControl may use MAVLink FTP for component metadata; P4 validates the allowlist against QGroundControl v5.1.5 and records any exception. */
        frame 'THR-003';
        frame 'THR-029';
        frame 'THR-050';
        frame 'THR-051';
        frame 'THR-057';
        attribute :>> method = VerificationMethod::'test';
        attribute :>> evidenceRepo = "P4";
        attribute :>> resiliencyApproach = ("Realignment: Restriction", "Coordinated Protection: Calibrated Defense-in-Depth");
    }
    satisfy 'SR-011' by UAS_Architecture::uasSystem.airVehicle.missionComputing.cc;
    requirement 'SR-012' : SecurityRequirement {
        doc /* The CC shall rate-limit MAVLink traffic forwarded to the FC to the approved per-message rates. */
        comment rationale /* Keeps a flood, malicious or accidental, from starving FC message handling. */
        frame 'THR-005';
        attribute :>> method = VerificationMethod::'test';
        attribute :>> evidenceRepo = "P4";
        attribute :>> resiliencyApproach = ("Privilege Restriction: Attribute-Based Usage Restriction");
    }
    satisfy 'SR-012' by UAS_Architecture::uasSystem.airVehicle.missionComputing.cc;
    requirement 'SR-013' : SecurityRequirement {
        doc /* The CC shall log each command it forwards to the FC with a timestamp and either the sending WireGuard peer or a CC-originated marker. */
        comment rationale /* WireGuard peers have individual keys, so the CC can attribute what MAVLink signing cannot. */
        frame 'THR-004';
        attribute :>> method = VerificationMethod::'test';
        attribute :>> evidenceRepo = "P4";
        attribute :>> resiliencyApproach = ("Analytic Monitoring: Forensic and Behavioral Analysis");
    }
    satisfy 'SR-013' by UAS_Architecture::uasSystem.airVehicle.missionComputing.cc;
    requirement 'SR-014' : SecurityRequirement {
        doc /* The CC shall accept only the USB device classes and identifiers on the approved payload list. */
        comment rationale /* Blocks a tampered payload from presenting itself as a keyboard, network adapter or storage device. */
        frame 'THR-011';
        frame 'THR-053';
        attribute :>> method = VerificationMethod::'test';
        attribute :>> evidenceRepo = "P4";
        attribute :>> resiliencyApproach = ("Realignment: Restriction");
    }
    satisfy 'SR-014' by UAS_Architecture::uasSystem.airVehicle.missionComputing.cc;
    requirement 'SR-015' : SecurityRequirement {
        doc /* The CC shall verify the signature of MAVLink frames received from the FC before using them for autonomy decisions. */
        comment rationale /* Autonomy acts only on telemetry from a key holder. */
        frame 'THR-052';
        attribute :>> method = VerificationMethod::'test';
        attribute :>> evidenceRepo = "P3";
        attribute :>> resiliencyApproach = ("Substantiated Integrity: Integrity Checks");
    }
    satisfy 'SR-015' by UAS_Architecture::uasSystem.airVehicle.missionComputing.cc;
    requirement 'SR-016' : SecurityRequirement {
        doc /* The CC shall restore C2 forwarding through a hardware watchdog when its C2 services stop responding. */
        comment rationale /* Shortens a CC hang before the data-link-loss failsafe ends the mission. The watchdog period is set in P4. */
        frame 'THR-009';
        attribute :>> method = VerificationMethod::'test';
        attribute :>> evidenceRepo = "P4";
        attribute :>> resiliencyApproach = ("Non-Persistence: Non-Persistent Services");
    }
    satisfy 'SR-016' by UAS_Architecture::uasSystem.airVehicle.missionComputing.cc;
    requirement 'SR-017' : SecurityRequirement {
        doc /* The CC shall encrypt stored mission imagery to a public key whose private key is held only on the MSS. */
        comment rationale /* A captured vehicle holds no key that decrypts its imagery. This follows the PX4 log-encryption design (SR-019). */
        frame 'THR-036';
        attribute :>> method = VerificationMethod::'demonstration';
        attribute :>> evidenceRepo = "P3";
        attribute :>> resiliencyApproach = ("Deception: Obfuscation");
    }
    satisfy 'SR-017' by UAS_Architecture::uasSystem.airVehicle.missionComputing.cc;
    requirement 'SR-018' : SecurityRequirement {
        doc /* The FC shall boot only firmware signed with the project firmware key, using PX4 Bootloader Secure Boot. */
        comment rationale /* Blocks unsigned or modified firmware loaded over USB or from tampered artifacts. PX4's secure boot uses Ed25519 signatures. Its root of trust is the boot loader in the FC's flash, with the trusted public keys compiled in; the PX4 boot loader sets no flash write-protection, so SR-018 holds only while SR-024 keeps the debug port closed. */
        frame 'THR-030';
        frame 'THR-041';
        frame 'THR-058';
        attribute :>> method = VerificationMethod::'test';
        attribute :>> evidenceRepo = "P2";
        attribute :>> resiliencyApproach = ("Substantiated Integrity: Integrity Checks", "Substantiated Integrity: Provenance Tracking");
    }
    satisfy 'SR-018' by UAS_Architecture::uasSystem.airVehicle.flightCritical.fc;
    requirement 'SR-019' : SecurityRequirement {
        doc /* The FC shall encrypt flight logs with PX4 log encryption, using a public key whose private key is held only on the MSS. */
        comment rationale /* PX4 log encryption (XChaCha20 with an RSA2048-OAEP key wrap) is not enabled in default builds, so it is a build requirement. */
        frame 'THR-028';
        attribute :>> method = VerificationMethod::'demonstration';
        attribute :>> evidenceRepo = "P3";
        attribute :>> resiliencyApproach = ("Deception: Obfuscation");
    }
    satisfy 'SR-019' by UAS_Architecture::uasSystem.airVehicle.flightCritical.fc;
    requirement 'SR-020' : SecurityRequirement {
        doc /* The FC shall run with the GNSS spoofing and jamming checks enabled (EKF2_GPS_CHECK bits 9 and 11 set). */
        comment rationale /* PX4 always alerts on receiver-reported spoofing and jamming. With these bits set, a report also fails PX4's GNSS checks on the ground and in flight, so the EKF stops relying on that data and arming is blocked. The default (2047) leaves bit 11 clear. Detection depends on the receiver reporting the condition. */
        frame 'THR-012';
        frame 'THR-024';
        frame 'THR-054';
        attribute :>> method = VerificationMethod::'inspection';
        attribute :>> evidenceRepo = "P6";
        attribute :>> resiliencyApproach = ("Analytic Monitoring: Monitoring and Damage Assessment", "Substantiated Integrity: Integrity Checks");
    }
    satisfy 'SR-020' by UAS_Architecture::uasSystem.airVehicle.flightCritical.fc;
    requirement 'SR-021' : SecurityRequirement {
        doc /* The FC shall take no automatic flight action on ADS-B traffic reports (NAV_TRAFF_AVOID = 0 or 1). */
        comment rationale /* With no ADS-B receiver in the system, any traffic report is spoofed. Return or Land on spoofed traffic would hand an adversary control of when the mission ends. */
        frame 'THR-050';
        attribute :>> method = VerificationMethod::'inspection';
        attribute :>> evidenceRepo = "P6";
        attribute :>> resiliencyApproach = ("Realignment: Restriction");
    }
    satisfy 'SR-021' by UAS_Architecture::uasSystem.airVehicle.flightCritical.fc;
    requirement 'SR-022' : SecurityRequirement {
        doc /* The FC shall have only the MAVLink instance for the CC link enabled besides USB, with the uXRCE-DDS client disabled (UXRCE_DDS_CFG = 0). */
        comment rationale /* Implements DD-03: no path to the FC bypasses the CC, and none bypasses signing. */
        frame 'THR-002';
        attribute :>> method = VerificationMethod::'inspection';
        attribute :>> evidenceRepo = "P6";
        attribute :>> resiliencyApproach = ("Realignment: Restriction", "Segmentation: Predefined Segmentation");
    }
    satisfy 'SR-022' by UAS_Architecture::uasSystem.airVehicle.flightCritical.fc;
    requirement 'SR-023' : SecurityRequirement {
        doc /* The FC shall carry tamper-evident seals over its SD-card slot, debug connectors and sensor and actuator wiring that are inspected before each flight. */
        comment rationale /* Physical access is the main threat to the key file and to internal wiring (PX4 hardening guide). Seals make that access evident before flight. */
        frame 'THR-013';
        frame 'THR-026';
        frame 'THR-027';
        frame 'THR-049';
        frame 'THR-055';
        frame 'THR-056';
        frame 'THR-065';
        attribute :>> method = VerificationMethod::'inspection';
        attribute :>> evidenceRepo = "P5";
        attribute :>> resiliencyApproach = ("Substantiated Integrity: Integrity Checks");
    }
    satisfy 'SR-023' by UAS_Architecture::uasSystem.airVehicle.flightCritical.fc;
    requirement 'SR-024' : SecurityRequirement {
        doc /* The FC shall have its SWD/JTAG debug port disabled or physically sealed in the flight configuration. */
        comment rationale /* PX4 notes that exposed debug ports allow a full firmware reflash and bypass all software security. That includes SR-018: over SWD the boot loader itself, and the keys it trusts, can be replaced. */
        frame 'THR-030';
        attribute :>> method = VerificationMethod::'test';
        attribute :>> evidenceRepo = "P5";
        attribute :>> resiliencyApproach = ("Realignment: Restriction");
    }
    satisfy 'SR-024' by UAS_Architecture::uasSystem.airVehicle.flightCritical.fc;
    requirement 'SR-025' : SecurityRequirement {
        doc /* The GCS shall alert the operator when FC telemetry is unsigned or not signed with the provisioned key. */
        comment rationale /* Detects a deleted or replaced key file and an adversary-installed first key before flight. Verified as part of VE-02. */
        frame 'THR-027';
        frame 'THR-045';
        frame 'THR-057';
        attribute :>> method = VerificationMethod::'demonstration';
        attribute :>> evidenceRepo = "P3";
        attribute :>> resiliencyApproach = ("Analytic Monitoring: Monitoring and Damage Assessment");
    }
    satisfy 'SR-025' by UAS_Architecture::uasSystem.groundSegment.gcs;
    requirement 'SR-026' : SecurityRequirement {
        doc /* The GCS shall require individual operator authentication to unlock a session. */
        comment rationale /* Prevents use of an unattended or stolen GCS, and ties actions to an operator account. */
        frame 'THR-016';
        frame 'THR-018';
        attribute :>> method = VerificationMethod::'inspection';
        attribute :>> evidenceRepo = "P6";
        attribute :>> resiliencyApproach = ("Privilege Restriction: Trust-Based Privilege Management");
    }
    satisfy 'SR-026' by UAS_Architecture::uasSystem.groundSegment.gcs;
    requirement 'SR-027' : SecurityRequirement {
        doc /* The GCS shall use full-disk encryption. */
        comment rationale /* Protects the keys and mission data on a lost or stolen laptop. */
        frame 'THR-016';
        frame 'THR-037';
        frame 'THR-038';
        attribute :>> method = VerificationMethod::'inspection';
        attribute :>> evidenceRepo = "P6";
        attribute :>> resiliencyApproach = ("Deception: Obfuscation");
    }
    satisfy 'SR-027' by UAS_Architecture::uasSystem.groundSegment.gcs;
    requirement 'SR-028' : SecurityRequirement {
        doc /* The GCS shall install only software packages whose signatures verify against the MSS release key. */
        comment rationale /* Keeps tampered QGroundControl builds and packages off a key holder. */
        frame 'THR-017';
        frame 'THR-019';
        attribute :>> method = VerificationMethod::'test';
        attribute :>> evidenceRepo = "P4";
        attribute :>> resiliencyApproach = ("Substantiated Integrity: Provenance Tracking");
    }
    satisfy 'SR-028' by UAS_Architecture::uasSystem.groundSegment.gcs;
    requirement 'SR-029' : SecurityRequirement {
        doc /* The GCS shall have no network interface enabled other than the ground-radio link during operations. */
        comment rationale /* The GCS is a key holder. Isolating it removes email, web and other network paths to the keys. */
        frame 'THR-019';
        attribute :>> method = VerificationMethod::'inspection';
        attribute :>> evidenceRepo = "P6";
        attribute :>> resiliencyApproach = ("Segmentation: Predefined Segmentation", "Realignment: Restriction");
    }
    satisfy 'SR-029' by UAS_Architecture::uasSystem.groundSegment.gcs;
    requirement 'SR-030' : SecurityRequirement {
        doc /* The GCS shall record each sortie's sent and received MAVLink traffic with the operator account that ran it. */
        comment rationale /* Gives the operator side of command attribution, which complements the CC log (SR-013). */
        frame 'THR-004';
        frame 'THR-018';
        attribute :>> method = VerificationMethod::'inspection';
        attribute :>> evidenceRepo = "P6";
        attribute :>> resiliencyApproach = ("Analytic Monitoring: Forensic and Behavioral Analysis");
    }
    satisfy 'SR-030' by UAS_Architecture::uasSystem.groundSegment.gcs;
    requirement 'SR-031' : SecurityRequirement {
        doc /* The MSS shall build release artifacts only from dependencies pinned by cryptographic hash to approved sources. */
        comment rationale /* Defeats typosquatting, dependency confusion and silent upstream changes. */
        frame 'THR-021';
        frame 'THR-025';
        frame 'THR-063';
        attribute :>> method = VerificationMethod::'test';
        attribute :>> evidenceRepo = "P4";
        attribute :>> resiliencyApproach = ("Substantiated Integrity: Provenance Tracking");
    }
    satisfy 'SR-031' by UAS_Architecture::uasSystem.mss;
    requirement 'SR-032' : SecurityRequirement {
        doc /* The MSS shall produce an SBOM and a vulnerability scan for every release artifact, including PX4 firmware. */
        comment rationale /* Tracks upstream advisories, including PX4 MAVLink fixes, against what is actually deployed. PX4 v1.18 generates an SPDX SBOM for each build. */
        frame 'THR-006';
        frame 'THR-063';
        attribute :>> method = VerificationMethod::'test';
        attribute :>> evidenceRepo = "P4";
        attribute :>> resiliencyApproach = ("Contextual Awareness: Dynamic Resource Awareness");
    }
    satisfy 'SR-032' by UAS_Architecture::uasSystem.mss;
    requirement 'SR-033' : SecurityRequirement {
        doc /* The MSS shall record build provenance for every release artifact and verify it before loading. */
        comment rationale /* Detects artifacts built outside the controlled pipeline or modified after build. */
        frame 'THR-021';
        frame 'THR-041';
        frame 'THR-063';
        attribute :>> method = VerificationMethod::'test';
        attribute :>> evidenceRepo = "P4";
        attribute :>> resiliencyApproach = ("Substantiated Integrity: Provenance Tracking");
    }
    satisfy 'SR-033' by UAS_Architecture::uasSystem.mss;
    requirement 'SR-034' : SecurityRequirement {
        doc /* The MSS shall hold software signing private keys in a hardware security module that does not export them. */
        comment rationale /* Even a compromised MSS cannot copy the signing keys. */
        frame 'THR-020';
        frame 'THR-023';
        frame 'THR-039';
        attribute :>> method = VerificationMethod::'demonstration';
        attribute :>> evidenceRepo = "P3";
        attribute :>> resiliencyApproach = ("Privilege Restriction: Attribute-Based Usage Restriction");
    }
    satisfy 'SR-034' by UAS_Architecture::uasSystem.mss;
    requirement 'SR-035' : SecurityRequirement {
        doc /* The MSS shall keep an encrypted offline backup of each software signing key. */
        comment rationale /* Losing a signing key would leave devices unable to accept updates. */
        frame 'THR-040';
        attribute :>> method = VerificationMethod::'demonstration';
        attribute :>> evidenceRepo = "P3";
        attribute :>> resiliencyApproach = ("Redundancy: Protected Backup and Restore");
    }
    satisfy 'SR-035' by UAS_Architecture::uasSystem.mss;
    requirement 'SR-036' : SecurityRequirement {
        doc /* The MSS shall provision a new MAVLink signing key to the FC, CC and GCS after any loss of physical custody of a key holder. */
        comment rationale /* The key is shared and PX4 has no automatic rotation, so one exposed holder exposes all of them. */
        frame 'THR-007';
        frame 'THR-016';
        frame 'THR-026';
        frame 'THR-034';
        frame 'THR-037';
        attribute :>> method = VerificationMethod::'demonstration';
        attribute :>> evidenceRepo = "P3";
        attribute :>> resiliencyApproach = ("Non-Persistence: Non-Persistent Information");
    }
    satisfy 'SR-036' by UAS_Architecture::uasSystem.mss;
    requirement 'SR-037' : SecurityRequirement {
        doc /* The MSS shall provision the first signing key on the FC over USB at first power-up, before any other link is connected. */
        comment rationale /* Closes the provisioning window created by PX4 v1.18 accepting the first key on any link. */
        frame 'THR-057';
        attribute :>> method = VerificationMethod::'demonstration';
        attribute :>> evidenceRepo = "P3";
        attribute :>> resiliencyApproach = ("Privilege Restriction: Trust-Based Privilege Management");
    }
    satisfy 'SR-037' by UAS_Architecture::uasSystem.mss;
    requirement 'SR-038' : SecurityRequirement {
        doc /* The MSS shall process offloaded vehicle data in an account that has no access to key material. */
        comment rationale /* Data returned from the vehicle is untrusted input to the host that holds every key. */
        frame 'THR-061';
        frame 'THR-062';
        attribute :>> method = VerificationMethod::'test';
        attribute :>> evidenceRepo = "P4";
        attribute :>> resiliencyApproach = ("Segmentation: Predefined Segmentation");
    }
    satisfy 'SR-038' by UAS_Architecture::uasSystem.mss;
    requirement 'SR-039' : SecurityRequirement {
        doc /* The MSS shall log each software load and key-provisioning action with the maintainer's identity. */
        comment rationale /* Makes maintenance actions attributable. */
        frame 'THR-022';
        attribute :>> method = VerificationMethod::'inspection';
        attribute :>> evidenceRepo = "P6";
        attribute :>> resiliencyApproach = ("Analytic Monitoring: Forensic and Behavioral Analysis");
    }
    satisfy 'SR-039' by UAS_Architecture::uasSystem.mss;
    requirement 'SR-040' : SecurityRequirement {
        doc /* The MSS shall require individual maintainer authentication. */
        comment rationale /* Prevents use of an unattended MSS and supports SR-039. */
        frame 'THR-020';
        frame 'THR-022';
        attribute :>> method = VerificationMethod::'inspection';
        attribute :>> evidenceRepo = "P6";
        attribute :>> resiliencyApproach = ("Privilege Restriction: Trust-Based Privilege Management");
    }
    satisfy 'SR-040' by UAS_Architecture::uasSystem.mss;
    requirement 'SR-041' : SecurityRequirement {
        doc /* The MSS shall record the firmware versions of the GNSS module, ESCs, radios and payload at each maintenance action and compare them with the approved baseline. */
        comment rationale /* Detects peripheral firmware changed through maintenance or replacement parts. */
        frame 'THR-011';
        frame 'THR-012';
        frame 'THR-013';
        attribute :>> method = VerificationMethod::'inspection';
        attribute :>> evidenceRepo = "P6";
        attribute :>> resiliencyApproach = ("Substantiated Integrity: Integrity Checks");
    }
    satisfy 'SR-041' by UAS_Architecture::uasSystem.mss;
    requirement 'SR-042' : SecurityRequirement {
        doc /* The MSS shall provision GCS keys over a direct wired connection and never through removable media. */
        comment rationale /* Removes the copy of the keys that removable media would leave behind. */
        frame 'THR-060';
        attribute :>> method = VerificationMethod::'inspection';
        attribute :>> evidenceRepo = "P6";
        attribute :>> resiliencyApproach = ("Non-Persistence: Non-Persistent Information");
    }
    satisfy 'SR-042' by UAS_Architecture::uasSystem.mss;
    requirement 'SR-043' : SecurityRequirement {
        doc /* The MSS shall generate and provision keys only while disconnected from external networks. */
        comment rationale /* Separates key handling from the online upstream intake (DF-16). */
        frame 'THR-023';
        frame 'THR-039';
        attribute :>> method = VerificationMethod::'inspection';
        attribute :>> evidenceRepo = "P6";
        attribute :>> resiliencyApproach = ("Non-Persistence: Non-Persistent Connectivity");
    }
    satisfy 'SR-043' by UAS_Architecture::uasSystem.mss;
    requirement 'SR-044' : SecurityRequirement {
        doc /* The CC shall accept maintenance connections only when authenticated with the MSS maintenance key. */
        comment rationale /* Stops a rogue device on the maintenance port from loading images or credentials. */
        frame 'THR-059';
        attribute :>> method = VerificationMethod::'test';
        attribute :>> evidenceRepo = "P4";
        attribute :>> resiliencyApproach = ("Privilege Restriction: Trust-Based Privilege Management");
    }
    satisfy 'SR-044' by UAS_Architecture::uasSystem.airVehicle.missionComputing.cc;
    requirement 'SR-045' : SecurityRequirement {
        doc /* The GCS shall alert the operator and refuse to arm the vehicle when the FC reports firmware older than the minimum approved release. */
        comment rationale /* PX4 Bootloader Secure Boot has no rollback check, so an older release signed with the project firmware key still boots (THR-066). PX4 reports its firmware version in AUTOPILOT_VERSION, so before each arming the GCS can compare it with the minimum release the MSS approved. This detects a downgrade before flight; it does not prevent the load. */
        frame 'THR-066';
        attribute :>> method = VerificationMethod::'test';
        attribute :>> evidenceRepo = "P3";
        attribute :>> resiliencyApproach = ("Substantiated Integrity: Integrity Checks");
    }
    satisfy 'SR-045' by UAS_Architecture::uasSystem.groundSegment.gcs;

    // 17 verification events (docs/08-verification-plan.md)
    verification 'VE-01' : SecurityVerification {
        doc /* Spoofed GCS heartbeats do not suppress the data-link-loss failsafe. Pass: FC enters Return within COM_DL_LOSS_T plus a stated tolerance; CC and GCS counters show injected packets dropped; control run shows the failsafe suppressed. */
        objective {
            verify 'SR-001';
            verify 'SR-002';
            verify 'SR-004';
        }
        attribute :>> method = VerificationMethod::'test';
        attribute :>> evidenceRepo = "P3";
    }
    verification 'VE-02' : SecurityVerification {
        doc /* Signed C2 works with the pinned versions. Pass: Signed commands execute; unsigned and wrongly signed commands have no effect; the GCS alerts on unsigned telemetry. Closes OI-01. */
        objective {
            verify 'SR-003';
            verify 'SR-025';
        }
        attribute :>> method = VerificationMethod::'demonstration';
        attribute :>> evidenceRepo = "P3";
    }
    verification 'VE-03' : SecurityVerification {
        doc /* CC accepts only signed, newer update images. Pass: Only the valid newer image installs; each rejection is logged. */
        objective {
            verify 'SR-007';
        }
        attribute :>> method = VerificationMethod::'test';
        attribute :>> evidenceRepo = "P3";
    }
    verification 'VE-04' : SecurityVerification {
        doc /* CC autonomy ignores unsigned or altered FC telemetry. Pass: Autonomy decisions use only frames with valid signatures; injected frames are logged and discarded. */
        objective {
            verify 'SR-015';
        }
        attribute :>> method = VerificationMethod::'test';
        attribute :>> evidenceRepo = "P3";
    }
    verification 'VE-05' : SecurityVerification {
        doc /* Imagery and flight logs are unreadable without the MSS key. Pass: Copies from the vehicle are unreadable; the MSS decrypts both. */
        objective {
            verify 'SR-017';
            verify 'SR-019';
        }
        attribute :>> method = VerificationMethod::'demonstration';
        attribute :>> evidenceRepo = "P3";
    }
    verification 'VE-06' : SecurityVerification {
        doc /* Key management on the MSS. Pass: Export fails; the restored key signs an artifact that verifies; after rotation the old key is rejected by FC, CC and GCS; first-key provisioning follows the defined order. */
        objective {
            verify 'SR-034';
            verify 'SR-035';
            verify 'SR-036';
            verify 'SR-037';
        }
        attribute :>> method = VerificationMethod::'demonstration';
        attribute :>> evidenceRepo = "P3";
    }
    verification 'VE-07' : SecurityVerification {
        doc /* CC verified boot and key sealing. Pass: Only the signed chain boots; the keys unseal only in the measured, unmodified boot state. */
        objective {
            verify 'SR-005';
            verify 'SR-010';
        }
        attribute :>> method = VerificationMethod::'test';
        attribute :>> evidenceRepo = "P2";
    }
    verification 'VE-08' : SecurityVerification {
        doc /* FC boots only signed firmware. Pass: Only the signed image starts PX4; the others stay in the bootloader. */
        objective {
            verify 'SR-018';
        }
        attribute :>> method = VerificationMethod::'test';
        attribute :>> evidenceRepo = "P2";
    }
    verification 'VE-09' : SecurityVerification {
        doc /* CC image hardening. Pass: Modified blocks fail to read; only the signing service reads the key; confined services cannot reach credentials; the device is refused; the watchdog restores C2 forwarding; the login is refused. */
        objective {
            verify 'SR-006';
            verify 'SR-008';
            verify 'SR-009';
            verify 'SR-014';
            verify 'SR-016';
            verify 'SR-044';
        }
        attribute :>> method = VerificationMethod::'test';
        attribute :>> evidenceRepo = "P4";
    }
    verification 'VE-10' : SecurityVerification {
        doc /* CC command filter and logging. Pass: Excluded messages never reach the FC; the approved command does; the flood is limited to the approved rate; each forwarded command is logged with time and WireGuard peer. */
        objective {
            verify 'SR-011';
            verify 'SR-012';
            verify 'SR-013';
        }
        attribute :>> method = VerificationMethod::'test';
        attribute :>> evidenceRepo = "P4";
    }
    verification 'VE-11' : SecurityVerification {
        doc /* Supply-chain pipeline and package integrity. Pass: Both bad builds fail; the release has an SBOM, a vulnerability scan and provenance; the tampered artifact and unsigned package are rejected; the offload account cannot read key material. */
        objective {
            verify 'SR-028';
            verify 'SR-031';
            verify 'SR-032';
            verify 'SR-033';
            verify 'SR-038';
        }
        attribute :>> method = VerificationMethod::'test';
        attribute :>> evidenceRepo = "P4";
    }
    verification 'VE-12' : SecurityVerification {
        doc /* Tamper-evident seal inspection. Pass: Seals cover every listed access point, and the SD-card access is visibly evident. */
        objective {
            verify 'SR-023';
        }
        attribute :>> method = VerificationMethod::'inspection';
        attribute :>> evidenceRepo = "P5";
    }
    verification 'VE-13' : SecurityVerification {
        doc /* FC debug port cannot be used. Pass: No debug session can be established, or the port is sealed so that any attempt is evident. */
        objective {
            verify 'SR-024';
        }
        attribute :>> method = VerificationMethod::'test';
        attribute :>> evidenceRepo = "P5";
    }
    verification 'VE-14' : SecurityVerification {
        doc /* FC parameter baseline. Pass: Bits 9 and 11 are set; NAV_TRAFF_AVOID is 0 or 1; uXRCE-DDS is disabled; only the CC-link MAVLink instance is enabled besides USB. */
        objective {
            verify 'SR-020';
            verify 'SR-021';
            verify 'SR-022';
        }
        attribute :>> method = VerificationMethod::'inspection';
        attribute :>> evidenceRepo = "P6";
    }
    verification 'VE-15' : SecurityVerification {
        doc /* GCS configuration. Pass: Individual logins and screen lock are enforced; the disk is encrypted; only the ground-radio interface is enabled; each sortie record names its operator. */
        objective {
            verify 'SR-026';
            verify 'SR-027';
            verify 'SR-029';
            verify 'SR-030';
        }
        attribute :>> method = VerificationMethod::'inspection';
        attribute :>> evidenceRepo = "P6";
    }
    verification 'VE-16' : SecurityVerification {
        doc /* MSS configuration and records. Pass: Individual logins; every load and provisioning action is logged with a maintainer; peripheral versions are recorded against the baseline; GCS keys are provisioned wired; key operations happen offline. */
        objective {
            verify 'SR-039';
            verify 'SR-040';
            verify 'SR-041';
            verify 'SR-042';
            verify 'SR-043';
        }
        attribute :>> method = VerificationMethod::'inspection';
        attribute :>> evidenceRepo = "P6";
    }
    verification 'VE-17' : SecurityVerification {
        doc /* GCS refuses to arm a vehicle with older FC firmware. Pass: With the older version the GCS alerts the operator and the vehicle stays disarmed; with the approved version it arms. */
        objective {
            verify 'SR-045';
        }
        attribute :>> method = VerificationMethod::'test';
        attribute :>> evidenceRepo = "P3";
    }
}
